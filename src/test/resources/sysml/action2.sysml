action action2 {
		
	first start;
	
	succession start then act1;
		
	action act1;
		
	succession act1 then act2;
	
	succession act1 then act3;
	
	action act2;
	
	action act3;
	
	succession act2 then done;
	
	succession act3 then done;

}
